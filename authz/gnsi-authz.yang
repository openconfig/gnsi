module gnsi-authz {
    yang-version 1.1;
    namespace "https://github.com/openconfig/gnsi/authz/yang";
    prefix gnsi-authz;

    import openconfig-system {
        prefix oc-sys;
    }
    import openconfig-types {
        prefix oc-types;
    }
    organization
        "Google LLC";

    contact
        "Google LLC";

    description
        "This module provides a data model for the metadata of the gRPC
         authorization policies installed on a networking device.";

    revision 2022-08-01 {
        description
            "Single authz policy.";
        reference "0.2.0";
    }

    revision 2022-01-17 {
        description
            "Initial revision.";
        reference "0.1.0";
    }

    typedef version {
        type string;
        description
            "The version ID of the gRPC authorization policy as provided by
             the gRPC Authorization Policy Manager when the policy was pushed.
             This leaf persists through a reboot.";
    }

    typedef created-on {
        type oc-types:timeticks64;
        description
            "The creation time of the gRPC authorization policy as reported by
             the gRPC Authorization Policy manager when the policy was pushed
             to the device. This value is reported as nanoseconds since epoch
             (January 1st, 1970 00:00:00 GMT). This leaf persists through
             a reboot.";
    }

    // gRPC server authorization policy related definitions.

    grouping grpc-server-authz-policy-state {
        description
            "gNMI server's gRPC authorization policy freshness-related data.";

        leaf grpc-authz-policy-version {
            type version;
            description
                "The version of the gRPC authorization policy that is used by
                 this system.";
        }
        leaf grpc-authz-policy-created-on {
            type created-on;
            description
                "The timestamp of the moment when the gRPC authorization policy
                that is currently used by this system was created.";
        }
    }

    // Augments section.

    augment "/oc-sys:system/oc-sys:aaa/oc-sys:authorization/" +
            "oc-sys:state" {
        description
            "A system's gRPC authorization policy freshness information.";

        uses grpc-server-authz-policy-state;
    }
}
