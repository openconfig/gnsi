module gnsi-telemetry {
    yang-version 1.1;
    namespace "https://github.com/openconfig/gnsi/yang";
    prefix gnsi;

    import gnsi-authz {
        prefix gnsi-authz;
    }
    import gnsi-certz {
        prefix gnsi-certz;
    }
    import gnsi-credentialz {
        prefix gnsi-credz;
    }
    import gnsi-pathz {
        prefix gnsi-pathz;
    }
    organization
        "Google LLC";

    contact
        "Google LLC";

    description
        "This module provides a data model for the metadata of credentials
        installed on a networking device.";

    revision 2022-09-20 {
        description
            "Updated to reflect change of gNSI.cert into gNSI.certz.";
        reference "0.4.0";
    }
    revision 2022-09-10 {
        description
            "Updated to reflect combination of gNSI.ssh and gNSI.console into
            gNSI.credentialz.";
        reference "0.3.0";
    }
    revision 2022-02-10 {
        description
            "Split into sub-api files.";
        reference "0.2.0";
    }
    revision 2022-01-07 {
        description
            "Initial revision.";
        reference "0.1.0";
    }

}
