module gnsi-ssh {
    yang-version 1.1;
    namespace "https://github.com/openconfig/gnsi/ssh/yang";
    prefix gnsi;

    import openconfig-system {
        prefix oc-sys;
    }
    import openconfig-types {
        prefix oc-types;
    }
    organization
        "Google LLC";

    contact
        "Google LLC";

    description
        "This module provides a data model for the metadata of SSH credentials
        installed on a networking device.";

    revision 2022-02-10 {
        description
            "Initial revision.";
        reference "0.1.0";
    }

    typedef version {
        type string;
        description
            "The version ID of the credential as provided by the credential
            manager when the credential was pushed. This leaf persists through
            a reboot.";
    }

    typedef created-on {
        type oc-types:timeticks64;
        description
            "The creation time of the credential as reported by the credential
            manager when the credential was pushed to the device. This value is
            reported as nanoseconds since epoch (January 1st, 1970 00:00:00 GMT).
            This leaf persists through a reboot.";
    }

    // SSH server related definitions.

    grouping ssh-server-credentials-version {
        description
            "SSH server credentials freshness-related data.";

        leaf active-trust-bundle-version {
            type version;
            description
                "The version of the bundle of the Certificate Authority
                certificates a.k.a. trust bundle.";
        }
        leaf active-trust-bundle-created-on {
            type created-on;
            description
                "The timestamp of the moment when the bundle of the Certificate
                Authority certificates (a.k.a. trust bundle) was created.";
        }
    }


    // System role SSH related definitions.

    grouping user-ssh-credentials-version {
        description
            "System role credentials freshness-related data.";

        leaf authorized-users-list-version {
            type version;
            description
                "The version of the list of authorized users that is currently
                associated with this system role.";
        }
        leaf authorized-users-list-created-on {
            type created-on;
            description
                "The timestamp of the moment the currently used list of
                authorized users has been created.";
        }
        leaf authorized-keys-list-version {
            type version;
            description
                "The version of the list of authorized keys that is currently
                associated with this system role.";
        }
        leaf authorized-keys-list-created-on {
            type created-on;
            description
                "The timestamp of the moment the currently used list of
                authorized keys has been created.";
        }
    }

    // Augments section.

    augment "/oc-sys:system/oc-sys:ssh-server/oc-sys:state" {
        description
            "SSH server credentials freshness data.";

        uses ssh-server-credentials-version;
    }
    augment "/oc-sys:system/oc-sys:aaa/oc-sys:authentication/oc-sys:users/" +
            "oc-sys:user/oc-sys:state" {
        description
            "A system role credentials freshness information.";

        uses user-ssh-credentials-version;
    }
    deviation  "/oc-sys:system/oc-sys:aaa/oc-sys:authentication/oc-sys:users/" +
            "oc-sys:user/oc-sys:config/oc-sys:ssh-key" {
        deviate not-supported;
    }
    deviation  "/oc-sys:system/oc-sys:aaa/oc-sys:authentication/oc-sys:users/" +
            "oc-sys:user/oc-sys:state/oc-sys:ssh-key" {
        deviate not-supported;
    }
}
