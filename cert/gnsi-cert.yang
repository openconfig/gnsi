module gnsi-cert {
    yang-version 1.1;
    namespace "https://github.com/openconfig/gnsi/cert/yang";
    prefix gnsi;

    import openconfig-system {
        prefix oc-sys;
    }
    import openconfig-system-grpc {
        prefix oc-sys-grpc;
    }
    import openconfig-types {
        prefix oc-types;
    }
    organization
        "Google LLC";

    contact
        "Google LLC";

    description
        "This module provides a data model for the metadata of gRPC credentials
        installed on a networking device.";

    revision 2022-02-10 {
        description
            "Initial revision.";
        reference "0.1.0";
    }

    typedef version {
        type string;
        description
            "The version ID of the credential as provided by the credential
            manager when the credential was pushed. This leaf persists through
            a reboot.";
    }

    typedef created-on {
        type oc-types:timeticks64;
        description
            "The creation time of the credential as reported by the credential
            manager when the credential was pushed to the device. This value is
            reported as nanoseconds since epoch (January 1st, 1970 00:00:00 GMT).
            This leaf persists through a reboot.";
    }

    // gRPC server related definitions.

    grouping grpc-server-credentials-config {
        description
            "Credential-related configuration data for a gRPC server.";

        leaf ca-trust-bundle-id {
            type string;
            description
                "The ID of the Certificate Authority trust bundle that is
                used by this gRPC server. The CA trust bundle is provisioned
                through other interfaces to the device, such as the gNSI
                certificate management service.";
        }
        leaf certificate-revocation-list-bundle-id {
            type string;
            description
                "The ID of the Certificate Revocation List (CRL) bundle that is
                used by this gRPC server. The CRL is provisioned through other
                interfaces to the device, such as the gNSI certificate
                management service.";
        }
    }

    grouping grpc-server-credentials-state {
        description
            "gRPC server credentials freshness-related data.";

        leaf certificate-version {
            type version;
            description
                "The version of the certificate (and associated
                private key) that is used by this gRPC server.";
        }
        leaf certificate-created-on {
            type created-on;
            description
                "The timestamp of the moment when the certificate
                (and associated private key) that is currently used
                by this gRPC server was created.";
        }
        leaf ca-trust-bundle-version {
            type version;
            description
                "The version of the bundle of the Certificate
                Authority certificates a.k.a. trust bundle used by
                this gRPC server.";
        }
        leaf ca-trust-bundle-created-on {
            type created-on;
            description
                "The timestamp of the moment when the bundle of
                the Certificate Authority certificates (a.k.a.
                trust bundle) was created.";
        }
        leaf certificate-revocation-list-bundle-version {
            type version;
            description
                "The version of the Certificate Revocation List bundle used by
                this gRPC server.";
        }
        leaf certificate-revocation-list-bundle-created-on {
            type created-on;
            description
                "The timestamp of the moment when the Certificate Revocation
                List bundle was created.";
        }
        uses grpc-server-credentials-config;
    }

    identity grpc-credential-entity-kind {
        description
            "Base identity for a credentials related entity.
            It defines its kind.";
    }

    identity certificate {
        base grpc-credential-entity-kind;

        description
            "A certificate identity.";
    }

    identity ca-trust-bundle {
        base grpc-credential-entity-kind;

        description
            "A Certificate Authority certificate bundle (a.k.a. trust bundle)
            identity.";
    }

    identity certificate-revocation-list-bundle {
        base grpc-credential-entity-kind;

        description
            "A Certificate Revocation List bundle identity.";
    }

    grouping grpc-credential-entity-state {
        description
            "Operational state data for an credential entity.";
        leaf id {
            type string;
            description
                "The ID of the credential entity.";
        }
        leaf kind {
            type identityref { base grpc-credential-entity-kind;}
            description
                "The type of the credential entity (certificate, CA trust bundle
                 or Certificate Revocation List bundle).";
        }

        leaf version {
            type version;
            description
                "The version of the credential entity.";
        }
        leaf created-on {
            type created-on;
            description
                "The timestamp of the moment when the credential entity was
                created.";
        }
    }

    grouping grpc-credential-entities {
        description
            "Collection of credential entities that have been installed on
             the device using the gNSI certificate management service.
             Each credential listed here is identified by an ID and has its
             version and creation date/time listed.";

        container entities {
            config false;
            description
                "Information about freshness of an entity (certificate, CA trust
                 bundle or Certificate Revocation List) that have been installed
                 on the device using the gNSI certificate management service.";

            list entity {
                key id;
                ordered-by system;
                description
                    "Information about the credential entity that is identified
                    by the `id`.";
                leaf id {
                    type leafref {
                        path "../state/id";
                    }
                    description
                        "The ID of the credential entity.";
                }
                container state {
                    description
                        "Operational state data for an credential entity.";

                    uses grpc-credential-entity-state;
                }
            }
        }
    }

    grouping system-grpc-server-credentials {
        description
            "Collection of credentials that have been installed on the device
             using the gNSI certificate management service.
             Each credential listed here is identified by an ID and has its
             version and creation date/time listed.";

        container grpc-credentials {
            config false;
            description
                "Collection of credentials that have been installed on
                 the device using the gNSI certificate management service.
                 Each credential listed here is identified by an ID and has its
                 version and creation date/time listed.";

            uses grpc-credential-entities;
        }
    }

    // Augments section.

    augment "/oc-sys:system" {
        description
            "Collection of credentials that have been installed on the device
             using the gNSI certificate management service.
             Each credential listed here is identified by an ID and has its
             version and creation date/time listed.";

        uses system-grpc-server-credentials;
    }
    augment "/oc-sys:system/oc-sys-grpc:grpc-servers/oc-sys-grpc:grpc-server/" +
            "oc-sys-grpc:config" {
        description
            "Configuration of credentials used by a gRPC server and managed
             by the gNSI certificate management service.";

        uses grpc-server-credentials-config;
    }
    augment "/oc-sys:system/oc-sys-grpc:grpc-servers/oc-sys-grpc:grpc-server/" +
            "oc-sys-grpc:state" {
        description
            "A gRPC server credentials freshness information.";

        uses grpc-server-credentials-state;
    }
}
