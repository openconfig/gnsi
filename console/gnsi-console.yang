module gnsi-console {
    yang-version 1.1;
    namespace "https://github.com/openconfig/gnoi/gnsi/console/yang";
    prefix gnsi;

    import openconfig-system {
        prefix oc-sys;
    }
    import openconfig-types {
        prefix oc-types;
    }
    organization
        "Google LLC";

    contact
        "Google LLC";

    description
        "This module provides a data model for the metadata of console
         credentials installed on a networking device.";

    revision 2022-02-10 {
        description
            "Initial revision.";
        reference "0.1.0";
    }

    typedef version {
        type string;
        description
            "The version ID of the credential as provided by the credential
            manager when the credential was pushed. This leaf persists through
            a reboot.";
    }

    typedef created-on {
        type oc-types:timeticks64;
        description
            "The creation time of the credential as reported by the credential
            manager when the credential was pushed to the device. This value is
            reported as nanoseconds since epoch (January 1st, 1970 00:00:00 GMT).
            This leaf persists through a reboot.";
    }

    // System role console related definitions.

    grouping user-console-credentials-version {
        description
            "System role credentials freshness-related data.";

        leaf password-version {
            type version;
            description
                "The version of the password that is currently used to
                authenticate this user account.";
        }
        leaf password-created-on {
            type created-on;
            description
                "The timestamp of the moment the currently used password has
                been created.";
        }
    }

    // Augments section.

    augment "/oc-sys:system/oc-sys:aaa/oc-sys:authentication/oc-sys:users/" +
            "oc-sys:user/oc-sys:state" {
        description
            "A system role credentials freshness information.";

        uses user-console-credentials-version;
    }
    deviation  "/oc-sys:system/oc-sys:aaa/oc-sys:authentication/oc-sys:users/" +
            "oc-sys:user/oc-sys:config/oc-sys:password" {
        deviate not-supported;
    }
    deviation  "/oc-sys:system/oc-sys:aaa/oc-sys:authentication/oc-sys:users/" +
            "oc-sys:user/oc-sys:config/oc-sys:password-hashed" {
        deviate not-supported;
    }
}
